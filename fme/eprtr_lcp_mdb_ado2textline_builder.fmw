FME workspace eprtr_lcp_mdb_ado2textline_builder.fmw

Parameters:
- SourceDataset_MDB_ADO =   # Database Path
- DestDataset_TEXTLINE_4 = $(FME_SERVER_DEST_DIR)\error_output.txt   # Destination Text File
- DestDataset_TEXTLINE = $(FME_SERVER_DEST_DIR)\eprtr_lcp_transformer.xml   # Destination Text File
- VERSION = 1   # Template version
- DestDataset_TEXTLINE_7 = $(FME_SERVER_DEST_DIR)\error_output.txt   # Destination Text File

Readers:
- MDB_ADO_1: MDB_ADO from $(SourceDataset_MDB_ADO)

Writers:
- TEXTLINE_1: TEXTLINE to $(DestDataset_TEXTLINE)
- TEXTLINE_2: TEXTLINE to $(DestDataset_TEXTLINE_7)
- TEXTLINE_3: TEXTLINE to $(DestDataset_TEXTLINE_4)

ProductionInstallationPartReport (reader MDB_ADO_1)
    attributes: ProductionInstallationPart_localId text(255), ProductionInstallationPart_namespace text(255), combustionPlantCategory text(255), furtherDetails text(255), numberOfOperatingHours double, withinRefinery yesno, proportionofUsefulHeatProductionForDistrictHeating double, remarks text(255), confidentialityReason text(255), ReportId long
    -> ListBuilder
ListBuilder
    GROUPS_ORDERED = No
    LIST_NAME = prod_install_list
    -> Aggregator
DesulphurisationInformationType (reader MDB_ADO_1)
    attributes: DesulphurisationInformationTypeId autonumber, ProductionInstallationPart_localId text(255), month text(255), desulphurisationRate double, sulphurContent double, technicalJustification text(255)
    -> ListBuilder_2
ListBuilder_2
    GROUPS_ORDERED = No
    LIST_NAME = desulphurisation_list
    -> Aggregator
EmissionsToAir (reader MDB_ADO_1)
    attributes: EmissionsToAirId autonumber, ProductionInstallationPart_localId text(255), pollutant text(255), totalPollutantQuantityTNE double, confidentialityReason text(255)
    -> ListBuilder_3
ListBuilder_3
    GROUPS_ORDERED = No
    LIST_NAME = emissions_list
    -> Aggregator
EnergyInput (reader MDB_ADO_1)
    attributes: EnergyInputId autonumber, ProductionInstallationPart_localId text(255), fuelInput text(255), otherSolidFuel text(255), otherGaseousFuel text(255), furtherDetails text(255), energyInputTJ double, confidentialityReason text(255)
    -> ListBuilder_4
ListBuilder_4
    GROUPS_ORDERED = No
    LIST_NAME = energy_list
    -> Aggregator
ProductionFacilityReport (reader MDB_ADO_1)
    attributes: ProductionFacility_localId text(255), ProductionFacility_namespace text(255), numberOfOperatingHours double, numberOfEmployees long, remarks text(255), representativeStackHeightM double, stackHeightClass text(255), confidentialityReason text(255), ReportId long
    -> ListBuilder_5
ListBuilder_5
    GROUPS_ORDERED = No
    LIST_NAME = prod_facility_list
    -> Aggregator
ProductionVolumeType (reader MDB_ADO_1)
    attributes: ProductionVolumeTypeId autonumber, ProductionFacility_localId text(255), productName text(255), productionVolume double, productionVolumeUnits text(255)
    -> ListBuilder_6
ListBuilder_6
    GROUPS_ORDERED = No
    LIST_NAME = prod_volume_list
    -> Aggregator
OffSiteWasteTransfer (reader MDB_ADO_1)
    attributes: OffsiteWasteTransferId autonumber, ProductionFacility_localId text(255), wasteClassification text(255), wasteTreatment text(255), totalWasteQuantityTNE double, methodCode text(255), methodClassification text(255), furtherDetails text(255), confidentialityReason text(255), nameOfReceiver text(255), Receiver_streetName text(255), Receiver_buildingNumber text(255), Receiver_city text(255), Receiver_postalCode text(255), Receiver_countryCode text(255), ReceivingSite_streetName text(255), ReceivingSite_buildingNumber text(255), ReceivingSite_city text(255), ReceivingSite_postalCode text(255), ReceivingSite_countryCode text(255)
    -> ListBuilder_7
ListBuilder_7
    GROUPS_ORDERED = No
    LIST_NAME = offw_list
    -> Aggregator
OffSiteWasteTransferMethodClassification (reader MDB_ADO_1)
    attributes: OffSiteWasteTransferMethodClassificationId autonumber, OffSiteWasteTransferId long, methodClassification text(255), furtherDetails text(255)
    -> ListBuilder_10
ListBuilder_10
    GROUPS_ORDERED = No
    LIST_NAME = offw_method_list
    -> Aggregator
OffSitePollutantTransfer (reader MDB_ADO_1)
    attributes: OffSitePollutantTransferId autonumber, ProductionFacility_localId text(255), pollutant text(255), totalPollutantQuantityKg double, methodCode text(255), methodClassification text(255), furtherDetails text(255), confidentialityReason text(255)
    -> ListBuilder_8
ListBuilder_8
    GROUPS_ORDERED = No
    LIST_NAME = offp_list
    -> Aggregator
OffSitePollutantTransferMethodClassification (reader MDB_ADO_1)
    attributes: OffSitePollutantTransferMethodClassificationId autonumber, OffSitePollutantTransferId long, methodClassification text(255), furtherDetails text(255)
    -> ListBuilder_11
ListBuilder_11
    GROUPS_ORDERED = No
    LIST_NAME = offp_method_list
    -> Aggregator
PollutantRelease (reader MDB_ADO_1)
    attributes: PollutantReleaseId autonumber, ProductionFacility_localId text(255), pollutant text(255), mediumCode text(255), totalPollutantQuantityKg double, AccidentalPollutantQuantityKG double, methodCode text(255), methodClassification text(255), furtherDetails text(255), confidentialityReason text(255)
    -> ListBuilder_9
ListBuilder_9
    GROUPS_ORDERED = No
    LIST_NAME = prelease_list
    -> Aggregator
PollutantReleaseMethodClassification (reader MDB_ADO_1)
    attributes: PollutantReleaseMethodClassificationId autonumber, PollutantReleaseId long, methodClassification text(255), furtherDetails text(255)
    -> ListBuilder_12
ListBuilder_12
    GROUPS_ORDERED = No
    LIST_NAME = prelease_method_list
    -> Aggregator
ReportData (reader MDB_ADO_1)
    attributes: ReportId autonumber, countryId text(255), reportingYear long
    -> Aggregator
VersionControl (reader MDB_ADO_1)
    attributes: TemplateVersion long
    -> Aggregator
Aggregator
    ACCUM_ATTRS_NAME = Merge Incoming Attributes
    MODE = Attributes Only
    ORDERED = No
    SEP = ,
    AGGREGATE -> VersionExists
VersionExists: Tester
    BOOL_OP = OR
    TEST_CLAUSE = TEST TemplateVersion NOT_ATTRIBUTE_IS_MISSING ""
    TEST_MODE = TEST
    PASSED -> CorrectVersion
    FAILED -> text_line (writer TEXTLINE_3)
CorrectVersion: Tester
    BOOL_OP = OR
    TEST_CLAUSE = TEST @Value(TemplateVersion) = $(VERSION)
    TEST_MODE = TEST
    PASSED -> XMLTemplater [ROOT]
    FAILED -> text_line (writer TEXTLINE_2)
XMLTemplater
    OUTPUT_XML_HEADER = Yes
    RESULT_ATTRIBUTE = text_line_data
    ROOT_QUERY_EXPR:
      <ReportData xmlns:xsi="http://www.w3.org/2001/XMLSchema-instance" xsi:noNamespaceSchemaLocation="http://dd.eionet.europa.eu/schemas/EPRTRandLCPintegration/eprtrlcp_v_1.0.xsd">
          <!-- Schema Version 1.3 | Created: 23.10.2017 | Last updated: 04.03.2019 -->
          <countryId>{fme:get-attribute("countryId")}</countryId>
          <reportingYear>{fme:get-attribute("reportingYear")}</reportingYear>
          {
      	let $PI_localId := fme:get-list-attribute("prod_install_list{}.ProductionInstallationPart_localId")
      	let $PI_namespace := fme:get-list-attribute("prod_install_list{}.ProductionInstallationPart_namespace")
      	let $PI_reason := fme:get-list-attribute("prod_install_list{}.confidentialityReason")
      	let $PI_op_hours := fme:get-list-attribute("prod_install_list{}.numberOfOperatingHours")
      	let $PI_useful_heat := fme:get-list-attribute("prod_install_list{}.proportionofUsefulHeatProductionForDistrictHeating")
      	let $PI_remarks := fme:get-list-attribute("prod_install_list{}.remarks")
      	let $PI_within_r := fme:get-list-attribute("prod_install_list{}.withinRefinery")
      	let $PI_plant_categ := fme:get-list-attribute("prod_install_list{}.combustionPlantCategory")
      	let $PI_fdetails := fme:get-list-attribute("prod_install_list{}.furtherDetails")
          for $PI_id at $i in $PI_localId
          return
          <ProductionInstallationPartReport>
              <confidentialityReason>{$PI_reason[$i]}</confidentialityReason>
              <InspireId>
                  <localId>{$PI_id}</localId>
                  <namespace>{$PI_namespace[$i]}</namespace>
              </InspireId>
      		{ if (string-length($PI_op_hours[$i])>0) then
      		<numberOfOperatingHours>{fn:format-number(xs:double($PI_op_hours[$i]),"0.######")}</numberOfOperatingHours>
      		else ''
      		}
      		{ if (string-length($PI_useful_heat[$i])>0) then
      		<proportionOfUsefulHeatProductionForDistrictHeating>{fn:format-number(xs:double($PI_useful_heat[$i]),"0.######")}</proportionOfUsefulHeatProductionForDistrictHeating>
      		else ''
      		}
      		<remarks>{$PI_remarks[$i]}</remarks>
      		<withinRefinery>{if (fn:compare(fn:lower-case($PI_within_r[$i]),"yes") = 0 or fn:compare(fn:lower-case($PI_within_r[$i]),"true") = 0) then "true" else "false"}</withinRefinery>
      		<combustionPlantCategory>
      			<combustionPlantCategory>{$PI_plant_categ[$i]}</combustionPlantCategory>
      			<furtherDetails>{$PI_fdetails[$i]}</furtherDetails>
      		</combustionPlantCategory>
      		{
      		let $DS_PI_id := fme:get-list-attribute("desulphurisation_list{}.ProductionInstallationPart_localId")
      		let $DS_rate := fme:get-list-attribute("desulphurisation_list{}.desulphurisationRate")
      		let $DS_month := fme:get-list-attribute("desulphurisation_list{}.month")
      		let $DS_sulphur := fme:get-list-attribute("desulphurisation_list{}.sulphurContent")
      		let $DS_justification := fme:get-list-attribute("desulphurisation_list{}.technicalJustification")

      		for $DS_id at $j in $DS_PI_id
      		where $DS_id = $PI_id
      		return
      		<desulphurisationInformation>
      			<desulphurisationRate>{fn:format-number(xs:double($DS_rate[$j]),"0.######")}</desulphurisationRate>
      			<month>{$DS_month[$j]}</month>
      			<sulphurContent>{fn:format-number(xs:double($DS_sulphur[$j]),"0.######")}</sulphurContent>
      			<technicalJustification>{$DS_justification[$j]}</technicalJustification>
      		</desulphurisationInformation>
      		}{
      		let $EM_PI_id := fme:get-list-attribute("emissions_list{}.ProductionInstallationPart_localId")
      		let $EM_reason := fme:get-list-attribute("emissions_list{}.confidentialityReason")
      		let $EM_pollutant := fme:get-list-attribute("emissions_list{}.pollutant")
      		let $EM_total := fme:get-list-attribute("emissions_list{}.totalPollutantQuantityTNE")

      		for $EM_id at $j in $EM_PI_id
      		where $EM_id = $PI_id
      		return
      		<emissionsToAir>
      			<confidentialityReason>{$EM_reason[$j]}</confidentialityReason>
      			<pollutant>{$EM_pollutant[$j]}</pollutant>
      			<totalPollutantQuantityTNE>{fn:format-number(xs:double($EM_total[$j]),"0.######")}</totalPollutantQuantityTNE>
      		</emissionsToAir>
      		}{
      		let $EN_PI_id := fme:get-list-attribute("energy_list{}.ProductionInstallationPart_localId")
      		let $EN_reason := fme:get-list-attribute("energy_list{}.confidentialityReason")
      		let $EN_TJ := fme:get-list-attribute("energy_list{}.energyInputTJ")
      		let $EN_fuel := fme:get-list-attribute("energy_list{}.fuelInput")
      		let $EN_details := fme:get-list-attribute("energy_list{}.furtherDetails")
      		let $EN_gaseousf :=fme:get-list-attribute("energy_list{}.otherGaseousFuel")
      		let $EN_solidf := fme:get-list-attribute("energy_list{}.otherSolidFuel")

      		for $EN_id at $j in $EN_PI_id
      		where $EN_id = $PI_id
      		return
      		<energyInput>
      			<confidentialityReason>{$EN_reason[$j]}</confidentialityReason>
      			<energyinputTJ>{fn:format-number(xs:double($EN_TJ[$j]),"0.######")}</energyinputTJ>
      			<fuelInput>
      				<fuelInput>{$EN_fuel[$j]}</fuelInput>
      				<furtherDetails>{$EN_details[$j]}</furtherDetails>
      				<otherGaseousFuel>{$EN_gaseousf[$j]}</otherGaseousFuel>
      				<otherSolidFuel>{$EN_solidf[$j]}</otherSolidFuel>
      			</fuelInput>
      		</energyInput>
      		}
          </ProductionInstallationPartReport>
          }{
      	let $PF_localId := fme:get-list-attribute("prod_facility_list{}.ProductionFacility_localId")
      	let $PF_namespace := fme:get-list-attribute("prod_facility_list{}.ProductionFacility_namespace")
      	let $PF_reason := fme:get-list-attribute("prod_facility_list{}.confidentialityReason")
      	let $PF_employees := fme:get-list-attribute("prod_facility_list{}.numberOfEmployees")
      	let $PF_hours := fme:get-list-attribute("prod_facility_list{}.numberOfOperatingHours")
      	let $PF_remarks := fme:get-list-attribute("prod_facility_list{}.remarks")
      	let $PF_stack := fme:get-list-attribute("prod_facility_list{}.representativeStackHeightM")
      	let $PF_stackClass := fme:get-list-attribute("prod_facility_list{}.stackHeightClass")

      	for $PF_id at $i in $PF_localId
          return
      	<ProductionFacilityReport>
      		<confidentialityReason>{$PF_reason[$i]}</confidentialityReason>
              <InspireId>
                  <localId>{$PF_id}</localId>
                  <namespace>{$PF_namespace[$i]}</namespace>
              </InspireId>
              { if (string-length($PF_employees[$i])>0) then
      		<numberOfEmployees>{$PF_employees[$i]}</numberOfEmployees>
      		else ''
      		}
      		{ if (string-length($PF_hours[$i])>0) then
      		<numberOfOperatingHours>{fn:format-number(xs:double($PF_hours[$i]),"0.######")}</numberOfOperatingHours>
      		else ''
      		}
      		<remarks>{$PF_remarks[$i]}</remarks>
      		{ if (string-length($PF_stack[$i])>0)
      		   then
      		      <representativeStackHeightM>{fn:format-number(xs:double($PF_stack[$i]),"0.######")}</representativeStackHeightM>
      		   else ''
      	    }{
      		let $PV_PF_id := fme:get-list-attribute("prod_volume_list{}.ProductionFacility_localId")
      		let $PV_volume := fme:get-list-attribute("prod_volume_list{}.productionVolume")
      		let $PV_units := fme:get-list-attribute("prod_volume_list{}.productionVolumeUnits")
      		let $PV_name := fme:get-list-attribute("prod_volume_list{}.productName")

      		for $PV_id at $j in $PV_PF_id
      		where $PV_id = $PF_id
      		return
      		<productionVolume>
      			<productionVolume>{fn:format-number(xs:double($PV_volume[$j]),"0.######")}</productionVolume>
      			<productionVolumeUnits>{$PV_units[$j]}</productionVolumeUnits>
      			<productName>{$PV_name[$j]}</productName>
      		</productionVolume>
      		}{
      		let $OW_PF_id := fme:get-list-attribute("offw_list{}.ProductionFacility_localId")
      		let $OW_pk_id := fme:get-list-attribute("offw_list{}.OffsiteWasteTransferId")
      		let $OW_reason := fme:get-list-attribute("offw_list{}.confidentialityReason")
      		let $OW_TNE := fme:get-list-attribute("offw_list{}.totalWasteQuantityTNE")
      		let $OW_w_classification := fme:get-list-attribute("offw_list{}.wasteClassification")
      		let $OW_w_treatment := fme:get-list-attribute("offw_list{}.wasteTreatment")
      		let $OW_details := fme:get-list-attribute("offw_list{}.furtherDetails")
      		let $OW_m_classification := fme:get-list-attribute("offw_list{}.methodClassification")
      		let $OW_m_code := fme:get-list-attribute("offw_list{}.methodCode")
      		let $OW_r_name := fme:get-list-attribute("offw_list{}.nameOfReceiver")
      		let $OW_r_rbuilding := fme:get-list-attribute("offw_list{}.Receiver_buildingNumber")
      		let $OW_r_rcity := fme:get-list-attribute("offw_list{}.Receiver_city")
      		let $OW_r_rcountry := fme:get-list-attribute("offw_list{}.Receiver_countryCode")
      		let $OW_r_rpostal := fme:get-list-attribute("offw_list{}.Receiver_postalCode")
      		let $OW_r_rstreet := fme:get-list-attribute("offw_list{}.Receiver_streetName")
      		let $OW_r_rsbuilding := fme:get-list-attribute("offw_list{}.ReceivingSite_buildingNumber")
      		let $OW_r_rscity := fme:get-list-attribute("offw_list{}.ReceivingSite_city")
      		let $OW_r_rscountry := fme:get-list-attribute("offw_list{}.ReceivingSite_countryCode")
      		let $OW_r_rspostal := fme:get-list-attribute("offw_list{}.ReceivingSite_postalCode")
      		let $OW_r_rsstreet := fme:get-list-attribute("offw_list{}.ReceivingSite_streetName")

      		let $OWM_OW_id := fme:get-list-attribute("offw_method_list{}.OffSiteWasteTransferId")
      		let $OWM_m_classification := fme:get-list-attribute("offw_method_list{}.methodClassification")
      		let $OWM_details := fme:get-list-attribute("offw_method_list{}.furtherDetails")


      		for $OW_id at $j in $OW_PF_id
      		where $OW_id = $PF_id
      		return
      		<offsiteWasteTransfer>
      			<confidentialityReason>{$OW_reason[$j]}</confidentialityReason>
      			<totalWasteQuantityTNE>{fn:format-number(xs:double($OW_TNE[$j]),"0.######")}</totalWasteQuantityTNE>
      			<wasteClassification>{$OW_w_classification[$j]}</wasteClassification>
      			<wasteTreatment>{$OW_w_treatment[$j]}</wasteTreatment>
      			<method>
      				<furtherDetails>{$OW_details[$j]}</furtherDetails>
      				{ for $OWM_id at $k in $OWM_OW_id
      					where $OWM_id = $OW_pk_id[$j]
      					return
      						<furtherDetails>{$OWM_details[$k]}</furtherDetails>
      				}
      				{ if (string-length($OW_m_classification[$j])>0) then
      				<methodClassification>{$OW_m_classification[$j]}</methodClassification>
                      else ''
      				}
      				{ for $OWM_id at $k in $OWM_OW_id
      					where $OWM_id = $OW_pk_id[$j]
      					return
      						<methodClassification>{$OWM_m_classification[$k]}</methodClassification>
      				}
      				<methodCode>{$OW_m_code[$j]}</methodCode>
      			</method>
      			<transboundaryTransfer>
      				<nameOfReceiver>{$OW_r_name[$j]}</nameOfReceiver>
      				<addressOfReceiver>
      					<buildingNumber>{$OW_r_rbuilding[$j]}</buildingNumber>
      					<city>{$OW_r_rcity[$j]}</city>
      					<countryCode>{$OW_r_rcountry[$j]}</countryCode>
      					<postalCode>{$OW_r_rpostal[$j]}</postalCode>
      					<streetName>{$OW_r_rstreet[$j]}</streetName>
      				</addressOfReceiver>
      				<addressOfReceivingSite>
      					<buildingNumber>{$OW_r_rsbuilding[$j]}</buildingNumber>
      					<city>{$OW_r_rscity[$j]}</city>
      					<countryCode>{$OW_r_rscountry[$j]}</countryCode>
      					<postalCode>{$OW_r_rspostal[$j]}</postalCode>
      					<streetName>{$OW_r_rsstreet[$j]}</streetName>
      				</addressOfReceivingSite>
      			</transboundaryTransfer>
      		</offsiteWasteTransfer>
      		}{
      		let $OP_PF_id := fme:get-list-attribute("offp_list{}.ProductionFacility_localId")
      		let $OP_pk_id := fme:get-list-attribute("offp_list{}.OffSitePollutantTransferId")
      		let $OP_reason := fme:get-list-attribute("offp_list{}.confidentialityReason")
      		let $OP_details := fme:get-list-attribute("offp_list{}.furtherDetails")
      		let $OP_m_classification := fme:get-list-attribute("offp_list{}.methodClassification")
      		let $OP_m_code := fme:get-list-attribute("offp_list{}.methodCode")
      		let $OP_pollutant := fme:get-list-attribute("offp_list{}.pollutant")
      		let $OP_quantity := fme:get-list-attribute("offp_list{}.totalPollutantQuantityKg")

      		let $OPM_OP_id := fme:get-list-attribute("offp_method_list{}.OffSitePollutantTransferId")
      		let $OPM_m_classification := fme:get-list-attribute("offp_method_list{}.methodClassification")
      		let $OPM_details := fme:get-list-attribute("offp_method_list{}.furtherDetails")

      		for $OP_id at $j in $OP_PF_id
      		where $OP_id = $PF_id
      		return
      		<offsitePollutantTransfer>
      			<confidentialityReason>{$OP_reason[$j]}</confidentialityReason>
      			<pollutant>{$OP_pollutant[$j]}</pollutant>
      			<totalPollutantQuantityKg>{fn:format-number(xs:double($OP_quantity[$j]),"0.######")}</totalPollutantQuantityKg>
      			<method>
      				<furtherDetails>{$OP_details[$j]}</furtherDetails>
      				{ for $OPM_id at $k in $OPM_OP_id
      					where $OPM_id = $OP_pk_id[$j]
      					return
      						<furtherDetails>{$OPM_details[$k]}</furtherDetails>
      				}
      				{ if (string-length($OP_m_classification[$j])>0) then
      				<methodClassification>{$OP_m_classification[$j]}</methodClassification>
                      else ''
      				}
      				{ for $OPM_id at $k in $OPM_OP_id
      					where $OPM_id = $OP_pk_id[$j]
      					return
      						<methodClassification>{$OPM_m_classification[$k]}</methodClassification>
      				}
      				<methodCode>{$OP_m_code[$j]}</methodCode>
      			</method>
      		</offsitePollutantTransfer>
      		}{
      		let $PR_PF_id := fme:get-list-attribute("prelease_list{}.ProductionFacility_localId")
      		let $PR_pk_id := fme:get-list-attribute("prelease_list{}.PollutantReleaseId")
      		let $PR_quantity := fme:get-list-attribute("prelease_list{}.AccidentalPollutantQuantityKG")
      		let $PR_reason := fme:get-list-attribute("prelease_list{}.confidentialityReason")
      		let $PR_details := fme:get-list-attribute("prelease_list{}.furtherDetails")
      		let $PR_medium_code := fme:get-list-attribute("prelease_list{}.mediumCode")
      		let $PR_m_classification := fme:get-list-attribute("prelease_list{}.methodClassification")
      		let $PR_m_code := fme:get-list-attribute("prelease_list{}.methodCode")
      		let $PR_pollutant := fme:get-list-attribute("prelease_list{}.pollutant")
      		let $PR_total := fme:get-list-attribute("prelease_list{}.totalPollutantQuantityKg")

      		let $PRM_PR_id := fme:get-list-attribute("prelease_method_list{}.PollutantReleaseId")
      		let $PRM_m_classification := fme:get-list-attribute("prelease_method_list{}.methodClassification")
      		let $PRM_details := fme:get-list-attribute("prelease_method_list{}.furtherDetails")

      		for $PR_id at $j in $PR_PF_id
      		where $PR_id = $PF_id
      		return
      		<pollutantRelease>
      			{ if (string-length($PR_quantity[$j])>0) then
      			<accidentalPollutantQuantityKg>{fn:format-number(xs:double($PR_quantity[$j]),"0.######")}</accidentalPollutantQuantityKg>
      			else ''
      			}
      			<confidentialityReason>{$PR_reason[$j]}</confidentialityReason>
      			<mediumCode>{$PR_medium_code[$j]}</mediumCode>
      			<pollutant>{$PR_pollutant[$j]}</pollutant>
      			<totalPollutantQuantityKg>{fn:format-number(xs:double($PR_total[$j]),"0.######")}</totalPollutantQuantityKg>
      			<method>
      				<furtherDetails>{$PR_details[$j]}</furtherDetails>
      				{ for $PRM_id at $k in $PRM_PR_id
      					where $PRM_id = $PR_pk_id[$j]
      					return
      						<furtherDetails>{$PRM_details[$k]}</furtherDetails>
      				}
      				{ if (string-length($PR_m_classification[$j])>0) then
      				<methodClassification>{$PR_m_classification[$j]}</methodClassification>
                      else ''
      				}
      				{ for $PRM_id at $k in $PRM_PR_id
      					where $PRM_id = $PR_pk_id[$j]
      					return
          					<methodClassification>{$PRM_m_classification[$k]}</methodClassification>
      				}
      				<methodCode>{$PR_m_code[$j]}</methodCode>
      			</method>
      		</pollutantRelease>
      		}{
      		if (string-length($PF_stackClass[$i])>0) then
          		<stackHeightClass>{$PF_stackClass[$i]}</stackHeightClass>
      			else ''
      		}
      	</ProductionFacilityReport>
      	}
      </ReportData>
    VISIBLE_QUERY_VALIDATE = Yes
    -> XMLFormatter
XMLFormatter
    COLLAPSE_EMPTY_ELEMENT = No
    FORMATTING_CHOICE = Pretty-Print XML
    INDENT_SIZE = 2
    LIST_NAME = _xml_error
    NAMESPACE_CLEANUP = No
    OUTPUT_ENCODING = utf-8
    REMOVE_ALL_COMMENT = No
    REMOVE_EMPTY_ELEMENT = No
    REPLACE_TABS_WITH_SPACES = yes
    SCHEMALOC_CLEANUP = No
    TEXT_INDENT = no
    WHITESPACE_HANDLING = Preserve all whitespace
    XML_ATTR_TEXT = text_line_data
    XML_INPUT_TYPE = Attribute Specifying XML Text
    XML_OUTPUT_ATTR = _xml_output
    XML_OUTPUT_TYPE = Attribute
    PASSED -> text_line (writer TEXTLINE_1)
text_line (writer TEXTLINE_1)
    attributes: text_line_data buffer
text_line (writer TEXTLINE_2)
    attributes: text_line_data buffer
text_line (writer TEXTLINE_3)
    attributes: text_line_data buffer
